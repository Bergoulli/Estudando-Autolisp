(defun c:lcha()
  (setq pt1 nil)
  (setq pt2 nil)
  (setq texto nil)
  (setq pt3 nil)
  (setq pt4 nil)
  (initget 1)
  (setq pt1 (getpoint "\nClique no primeiro ponto: "))
  (initget 1)
  (setq pt2 (getpoint pt1 "\nClique no segundo ponto: "))
  (initget 1)
  (setq texto (getstring "\nDigite o identificador desejado: "))
  (setq pt3 (polar pt2 (angle pt2 pt1) 5))
  (setq pt4 (polar pt1 (angle pt1 pt2) 5))
  (command "layer" "n" "locação" "c" "1" "locação" "")
  (command "line" pt1 pt3 "")
  (command "chprop" "l" "" "la" "locação" "")
  (command "pline" pt1 "w" "0" "1" pt4 "")
  (command "chprop" "l" "" "la" "locação" "")
  (command "circle" pt2 "5")
  (command "chprop" "l" "" "la" "locação" "")
  (command "text" "j" "mc" pt2 "4" "0" texto)
  (command "chprop" "l" "" "la" "locação" "")
)

(defun c:i()
  (initget 1)
  (setq pti (getpoint "\nClique no ponto de geração da tabela: "))
  (setq xi (car pti))
  (setq yi (cadr pti))
  (setq pti2 (list (+ 65 xi) yi))
  (setq pti3 (list (+ 65 xi) (+ 5 yi)))
  (setq pti4 (list xi (+ 5 yi)))
  (setq pti5 (list (+ 5 xi) yi))
  (setq pti6 (list (+ 35 xi) yi))
  (setq pti7 (list (+ 5 xi) (+ 5 yi)))
  (setq pti8 (list (+ 35 xi) (+ 5 yi)))
  (setq pti9 (polar pti4 (angle pti4 pti5) (/ (distance pti4 pti5) 2)))
  (setq pti10 (polar pti7 (angle pti7 pti6) (/ (distance pti7 pti6) 2)))
  (setq pti11 (polar pti8 (angle pti8 pti2) (/ (distance pti8 pti2) 2)))
  (command "line" pti pti2 pti3 pti4 pti "")
  (command "line" pti5 pti7 "")
  (command "line" pti8 pti6 "")
  (command "text" "j" "mc" pti9 "2" "0" "iD")
  (command "text" "j" "mc" pti10 "2" "0" "COORDENADA X")
  (command "text" "j" "mc" pti11 "2" "0" "COORDENADA Y")
  (princ)
)
