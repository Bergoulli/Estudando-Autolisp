(defun c:lcha()
  (setq pt1 nil)
  (setq pt2 nil)
  (setq texto nil)
  (setq pt3 nil)
  (setq pt4 nil)
  (initget 1)
  (setq pt1 (getpoint "\nClique no primeiro ponto: "))
  (initget 1)
  (setq pt2 (getpoint pt1 "\nClique no segundo ponto: "))
  (initget 1)
  (setq texto (getstring "\nDigite o identificador desejado: "))
  (setq pt3 (polar pt2 (angle pt2 pt1) 5))
  (setq pt4 (polar pt1 (angle pt1 pt2) 5))
  (command "layer" "n" "locação" "c" "1" "locação" "")
  (command "line" pt1 pt3 "")
  (command "chprop" "l" "" "la" "locação" "")
  (command "pline" pt1 "w" "0" "1" pt4 "")
  (command "chprop" "l" "" "la" "locação" "")
  (command "circle" pt2 "5")
  (command "chprop" "l" "" "la" "locação" "")
  (command "text" "j" "mc" pt2 "4" "0" texto)
  (command "chprop" "l" "" "la" "locação" "")
)
